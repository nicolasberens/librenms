ADH-NETCOM-MIB DEFINITIONS ::= BEGIN

IMPORTS
	MODULE-IDENTITY,
	OBJECT-IDENTITY,
	OBJECT-TYPE,
	Integer32,
	enterprises
		FROM SNMPv2-SMI
	DisplayString
		FROM SNMPv2-TC;

 

environmentalTechnology MODULE-IDENTITY
	LAST-UPDATED "201503090000Z"
	ORGANIZATION "Environmental Technology Inc."
	CONTACT-INFO
		"	Environmental Technology Inc.
			Product Support

		Postal: 1850 N. Sheridan St.
			South Bend, IN 46628
			USA

		   Tel: +1 574 233 1202

		E-mail: cgartland@networketi.com"
	DESCRIPTION
		"The Structure of Management Information for 
		  Environmental Technology Inc. SNMP devices"
	REVISION      "201503090000Z"
	DESCRIPTION
		"ADH NETCOM: Ethernet-enabled air dehydrator."
	::= { enterprises 32185 }	--  assigned by IANA


netcom OBJECT-IDENTITY
	STATUS current
	DESCRIPTION
		" ADH NETCOM"
	::= { environmentalTechnology 2 }

-- this is the MIB for the ADH NETCOM air dehydrator family
-- for version 15 of the software or later : adding traps

statusInfo  OBJECT IDENTIFIER ::= { netcom 1 }
paramsInfo  OBJECT IDENTIFIER ::= { netcom 2 }
trapInfo    OBJECT IDENTIFIER ::= { netcom 3 }

-- statusInfo: gives state of the ADH NETCOM device
-- these change fairly frequently

allStatuses OBJECT-TYPE
        SYNTAX     DisplayString (SIZE (80))
        MAX-ACCESS read-only
        STATUS     current
        DESCRIPTION
                "Summary: same as objects 2-7, separated by semicolons"
        ::= { statusInfo 1 }
-- this is included as a convenience
-- if you are concerned that all the information you get is valid at exactly
-- the same time, use this instead of individual objects

pressurePSI OBJECT-TYPE
        SYNTAX     DisplayString (SIZE (10))
        MAX-ACCESS read-only
        STATUS     current
        DESCRIPTION
                "Pressure, in PSI or mbar"
        ::= { statusInfo 2 }

dutycycle OBJECT-TYPE
        SYNTAX     DisplayString (SIZE (10))
        MAX-ACCESS read-only
        STATUS     current
        DESCRIPTION
                "Current duty cycle, in percent; --- if none available"
        ::= { statusInfo 3 }

statusVars OBJECT-TYPE
        SYNTAX     DisplayString (SIZE (6))
        MAX-ACCESS read-only
        STATUS     current
        DESCRIPTION
                "Summary of the status of the unit.
		 Is always 7 characters
		 Character 1 is super-state: govering whole system, if 
				this unit is a master
				S=slave (not a master)
				M=master; N=master but system off line
				D=director; D=director but system off line
				master: for redundant systems
				director: for increasing pumping capability
                 Character 2 is major state: N=normal, S=standby, L=leaky
                 Character 3 is environment: N=normal, C=cold, H=hot
                 Character 4 is canister 1 condition:
                      O=OK (ie dry), F=full (wet), U=unknown, D=dead
                 Character 5 is canister 1 usage:
                      I=idle, U=in use, R=regenerating
                 Character 6 is canister 2 condition, as in character 4
                 Character 7 is canister 2 usage, as in character 5"
        ::= { statusInfo 4 }

temperature OBJECT-TYPE
        SYNTAX     DisplayString (SIZE (10))
        MAX-ACCESS read-only
        STATUS     current
        DESCRIPTION
                "Current temperature, in degrees F or C"
        ::= { statusInfo 5 }

alarms OBJECT-TYPE
        SYNTAX     DisplayString (SIZE (30))
        MAX-ACCESS read-only
        STATUS     current
        DESCRIPTION
                "Current alarm conditions: is a list of them
                 Each character has a - for no alarm, or an A or W if there
                 is an alarm.  A means alarm (serious), W means a warning
                 (not so serious).  Severity levels may later change.
		 List of alarms: (later versions may add more):
		 A1:  Low pressure
		 A2:  High pressure
		 W3:  High duty cycle
		 W4:  High temperature
		 W5:  Low temperature
		 W6:  Unused
		 A7:  Canister 1 won't heat
		 A8:  Canister 1 won't cool
		 A9:  Canister 2 won't heat
		 A10: Canister 2 won't cool
		 A11: Unable to pressurize
		 A12: Dew point alarm
		 W13: Compressor timeout (for future use)
		 W14: Communications error
		 A15: Canister 1 thermistor bad
		 A16: Canister 2 thermistor bad
		 A17: Ambient thermistor bad
		 A18: Overpressure
		 A19: Bad calibrations in EEPROM
		 A20: Bad limits in EEPROM
		 A21: Short cycling
		 A22: Pump shut down due to error condition"  		 
        ::= { statusInfo 6 }

compressorHours OBJECT-TYPE
        SYNTAX     DisplayString (SIZE (30))
        MAX-ACCESS read-only
        STATUS     current
        DESCRIPTION
                "Number of hours that the compressor has been running;
		 resolution is tenths of an hour."
        ::= { statusInfo 7 }


majorState OBJECT-TYPE
        SYNTAX INTEGER {
          online (1),
          standby (2),
          leaky (3)
          }
        MAX-ACCESS read-write
        STATUS current
        DESCRIPTION
	  "Major state of the dehydrator.
           Online: currently pressurizing.
           Standby: not pressurizing.
           Leaky: shut down because of inability to pressurize."
        ::= { statusInfo 8 }

--  This is the one of two writable variables in this MIB
--  Setting it will change the state of the system, if allowed.
--  The only valid changes are between online and standby.

cycleTime OBJECT-TYPE
        SYNTAX     DisplayString (SIZE (10))
        MAX-ACCESS read-only
        STATUS     current
        DESCRIPTION
                "Time of last duty cycle in seconds;
		 0.0 means none available"
        ::= { statusInfo 9}


-- paramsInfo: operating parameters of the ADH-NETCOM
-- these change infrequently if at all; mostly set at initialization
-- these will be settable via the configuration option of the web interface

lowerLimit OBJECT-TYPE
        SYNTAX     DisplayString (SIZE (10))
        MAX-ACCESS read-only
        STATUS     current
        DESCRIPTION
                "The pressure, in PSI or mbar,
		  at which the unit starts to pump"
        ::= { paramsInfo 1 }

upperLimit OBJECT-TYPE
        SYNTAX     DisplayString (SIZE (10))
        MAX-ACCESS read-only
        STATUS     current
        DESCRIPTION
                "The pressure, in PSI or mbar, which the unit pressurizes to"
        ::= { paramsInfo 2 }

lowerAlarmLimit OBJECT-TYPE
        SYNTAX     DisplayString (SIZE (10))
        MAX-ACCESS read-only
        STATUS     current
        DESCRIPTION
                "The pressure, in PSI or mbar,
		 below which the unit declares a low pressure alarm"
        ::= { paramsInfo 3 }

upperAlarmLimit OBJECT-TYPE
        SYNTAX     DisplayString (SIZE (10))
        MAX-ACCESS read-only
        STATUS     current
        DESCRIPTION
                "The pressure, in PSI or mbar,
		 above which the unit declares a high pressure alarm"
        ::= { paramsInfo 4 }


-- trapInfo: for trap, which comes in when alarm is set or cleared
trapString OBJECT-TYPE
        SYNTAX     DisplayString (SIZE (30))
        MAX-ACCESS read-only
        STATUS     current
        DESCRIPTION
                "Current alarm conditions: is a list of them
                 Each character has a - for no alarm, or a + if there
		 is an alarm
		 This is the variable that is sent by a trap event.
		 List of alarms: (later versions may add more):
		 1:  Low pressure
		 2:  High pressure
		 3:  High duty cycle
		 4:  High temperature
		 5:  Low temperature
		 6:  Unused
		 7:  Canister 1 won't heat
		 8:  Canister 1 won't cool
		 9:  Canister 2 won't heat
		 10: Canister 2 won't cool
		 11: Unable to pressurize
		 12: Dew point alarm
		 13: Compressor timeout (for future use)
		 14: Communications error
		 15: Canister 1 thermistor bad
		 16: Canister 2 thermistor bad
		 17: Ambient thermistor bad
		 18: Overpressure
		 19: Bad calibrations in EEPROM
		 20: Bad limits in EEPROM
		 21: Short cycling
		 22: Pump shut down due to error condition"  		 
        ::= { trapInfo 1 }



trapTrigger OBJECT-TYPE
       SYNTAX INTEGER {
          idle (0),
          trigger (1)
          }
        MAX-ACCESS read-write
        STATUS current
        DESCRIPTION
	   "Value: 0 or 1
	    Writing 1 causes a trap to be sent.
	    Writing 0 has no effect
 	    This will have no effect if traps are not enabled."
        ::= { trapInfo 2 }

--  This is the one of two writable variable in this MIB
--  It is included to let the user test trap sending/receiving.


END
